## REQ-001
- The system shall display the welcome message.

## REQ-002
- When the user presses the button, the system shall shut down.

## REQ-003
- If the battery level drops below 10%, then the system shall activate power saving mode.

## REQ-004
- While the aircraft is in flight, the system shall disable the landing gear lever.

## REQ-005
- Where the GPS module is installed, the system shall record location data.

## REQ-006
- The system should be fast.

## REQ-007
- The user interface must be user friendly and easy to use.

## REQ-008
- Calculated values are displayed by the system.

## REQ-009
- The system shall do X and Y.
